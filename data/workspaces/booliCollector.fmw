FME workspace booliCollector.fmw

Parameters:
- SourceDataset_POSTGIS = amazonHilding   # Connection
- DestDataset_FFS = $(FME_MF_DIR)kommuner.ffs   # Destination FME Feature Store (FFS) File
- SourceDataset_FFS = $(FME_MF_DIR)kommuner.ffs   # Source FME Feature Store (FFS) File(s)
- DestDataset_POSTGIS = amazonHilding   # Connection

Readers:
- POSTGIS_1: POSTGIS from $(SourceDataset_POSTGIS)
- FFS_2: FFS from $(SourceDataset_FFS)

Writers:
- FFS_1: FFS to $(DestDataset_FFS)
- POSTGIS_2: POSTGIS to $(DestDataset_POSTGIS)

h4s.kommuner (reader FFS_2)
    attributes: kommunkod varchar(200), kommunnamn varchar(200), lansnamn varchar(200), lanskod varchar(200), booli_id varchar(200)
    -> HTTPCaller
h4s.kommuner (reader POSTGIS_1) [off]
    attributes: kommunkod varchar(200), kommunnamn varchar(200), lansnamn varchar(200), lanskod varchar(200), booli_id varchar(200)
    -> HTTPCaller
    -> h4s.kommuner (writer FFS_1)
h4s.kommuner (writer FFS_1) [off]
    attributes: kommunkod varchar(200), kommunnamn varchar(200), lansnamn varchar(200), lanskod varchar(200), booli_id varchar(200)
HTTPCaller
    HTTP_METHOD = GET
    ERROR_ATTR = _error
    FOLLOW_REDIRECTS = Yes
    STATUS_CODE_ATTR = _http_status_code
    USE_COOKIES = No
    TARGET_ATTR = _response_body
    TARGET_ATTR_ENCODING = utf-8
    RESPONSE_HEADER_LIST_ATTR = _headers
    VERIFY_SSL_CERTIFICATES = Yes
    TARGET_URL = https://www.booli.se/api/proxy?
    ADDITIONAL_URL_PARAMETERS = url;/sold?areaId=@Value(booli_id)&limit=20&objectType=villa, lägenhet, parhus,radhus,kedjehus
    TRANSFER_TIMEOUT_LENGTH = 90
    CONNECTION_TIMEOUT_LENGTH = 60
    SAVE_FILE = Attribute
    -> JSONExtractor
JSONExtractor
    JSON_DOCUMENT = @Value(_response_body)
    EXTRACT_QUERY_TABLE = body json["body"]
    EVALUATED -> JSONFragmenter
    EVALUATED -> JSONExtractor_Evaluated
JSONExtractor_Evaluated: Inspector
JSONFragmenter
    JSON_QUERY = json[*][*]
    JSON_ATTR = body
    EXTRACT_ATTR = No
    FRAGMENTS -> Tester
Tester
    BOOL_OP = OR
    TEST_DESCRIPTION = ""
    TEST_CLAUSE = TEST @Value(json_type) NOT_= number
    TEST_MODE = Automatic
    PASSED -> JSONExtractor_3
JSONExtractor_3
    JSON_DOCUMENT = @Value(body)
    EXTRACT_QUERY_TABLE = latitude json["location"]["position"]["latitude"] longitude json["location"]["position"]["longitude"] municipality json["location"]["region"]["municipalityName"] county json["location"]["region"]["countyName"] type json["objectType"] booli_objectid json["booliId"] soldprice json["soldPrice"] livingarea json["livingArea"] pos json["url"]
    EVALUATED -> Tester_2
Tester_2
    BOOL_OP = OR
    TEST_DESCRIPTION = ""
    TEST_CLAUSE = TEST @Value(livingarea) ATTRIBUTE_HAS_VALUE ""
    TEST_MODE = Automatic
    PASSED -> AttributeCreator
AttributeCreator
    ATTR_TABLE = SET_TO sqm_cost = @Evaluate(@Value(soldprice)/@Value(livingarea))
    -> AttributeManager
AttributeManager
    ATTR_TABLE:
      REMOVE kommunkod
      REMOVE kommunnamn
      REMOVE lansnamn
      REMOVE lanskod
      REMOVE _headers{}.name
      REMOVE _headers{}.value
      REMOVE _response_body
      REMOVE _http_status_code
      REMOVE body
      REMOVE pos
    -> VertexCreator
VertexCreator
    XVAL = @Value(longitude)
    MODE_NAME = Replace with Point
    YVAL = @Value(latitude)
    -> CoordinateSystemSetter
CoordinateSystemSetter
    COORDSYS = EPSG:4326
    -> VertexCreator_Output
    -> h4s.booli_sold (writer POSTGIS_2)
VertexCreator_Output: Inspector
h4s.booli_sold (writer POSTGIS_2)
    attributes: booli_id int8, json_type varchar(200), json_index varchar(200), latitude varchar(200), longitude varchar(200), municipality varchar(200), county varchar(200), type varchar(200), booli_objectid varchar(200), soldprice varchar(200), livingarea varchar(200), sqm_cost float8
JSONExtractor_2
    JSON_DOCUMENT = @Value(body)
    EXTRACT_QUERY_TABLE = areaID json["areas"][0]["booliId"] areaTyp json["areas"][0]["types"][0]
