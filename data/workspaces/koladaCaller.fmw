FME workspace koladaCaller.fmw

Parameters:
- SourceDataset_POSTGIS = amazonHilding   # Connection
- DestDataset_POSTGIS = amazonHilding   # Connection
- SourceDataset_POSTGIS_2 = amazonHilding   # Connection

Readers:
- POSTGIS_1: POSTGIS from $(SourceDataset_POSTGIS)
- POSTGIS_3: POSTGIS from $(SourceDataset_POSTGIS_2)

Writers:
- POSTGIS_2: POSTGIS to $(DestDataset_POSTGIS)

h4s.kommunerOld (reader POSTGIS_1)
    attributes: kommunkod varchar(200), kommunnamn varchar(200), lansnamn varchar(200), lanskod varchar(200), booli_id varchar(200),BTREE
    -> AttributeManager
AttributeManager
    ATTR_TABLE = SET_TO newKod = @Value(kommunkod)
    -> Tester
Tester
    TEST_MODE = Automatic
    TEST_CLAUSE = NUM_TEST @Value(newKod) < 1000
    BOOL_OP = OR
    TEST_DESCRIPTION = ""
    PASSED -> StringPadder
    FAILED -> HTTPCaller_3
StringPadder
    BLANK_ATTRIBUTE = Yes
    SIDE = Left
    SRC_ATTRS = newKod
    PADCHAR = 0
    WIDTH = 4
    -> HTTPCaller_3
HTTPCaller_3: Junction
    -> HTTPCaller
    -> HTTPCaller_2
Note: N01951 - befolkning
HTTPCaller
    ERROR_ATTR = _error
    USE_COOKIES = No
    RESPONSE_HEADER_LIST_ATTR = _headers
    HTTP_METHOD = GET
    STATUS_CODE_ATTR = _http_status_code
    VERIFY_SSL_CERTIFICATES = Yes
    TARGET_ATTR_ENCODING = auto-detect
    FOLLOW_REDIRECTS = Yes
    TARGET_URL = http://api.kolada.se/v2/data/kpi/U00408/municipality/@Value(newKod)/year/2014,2015,2016
    SAVE_FILE = Attribute
    TRANSFER_TIMEOUT_LENGTH = 90
    TARGET_ATTR = _response_body
    CONNECTION_TIMEOUT_LENGTH = 60
    -> PythonCaller
PythonCaller
    PYTHONSYMBOL = processFeature
    NEW_ATTRIBUTES = result
    PYTHONSOURCE:
      import fme
      import fmeobjects
      import json
      # Template Function interface:
      # When using this function, make sure its name is set as the value of
      # the 'Class or Function to Process Features' transformer parameter
      def processFeature(feature):
          inJson = json.loads(feature.getAttribute("_response_body"))
          selectedList = inJson["values"]
          result = ""
          for i in range(len(selectedList)):
              cand = selectedList[i]["values"][-1]["value"]
              if result is "" and cand!="null" and cand!="_":
                  result=str(cand)
                  break
          feature.setAttribute("result",str(result))
    -> AttributeManager_3
AttributeManager_3
    ATTR_TABLE:
      REMOVE kommunnamn
      REMOVE lansnamn
      REMOVE lanskod
      REMOVE booli_id
      REMOVE newKod
      REMOVE _headers{}.name
      REMOVE _headers{}.value
      REMOVE _response_body
      REMOVE _http_status_code
      RENAME_SET_VALUE result > NMI
    -> FeatureMerger [REQUESTOR]
Note: N00900 - skattesats
HTTPCaller_2
    ERROR_ATTR = _error
    USE_COOKIES = No
    RESPONSE_HEADER_LIST_ATTR = _headers
    HTTP_METHOD = GET
    STATUS_CODE_ATTR = _http_status_code
    VERIFY_SSL_CERTIFICATES = Yes
    TARGET_ATTR_ENCODING = auto-detect
    FOLLOW_REDIRECTS = Yes
    TARGET_URL = http://api.kolada.se/v2/data/kpi/N00900/municipality/@Value(newKod)/year/2016
    SAVE_FILE = Attribute
    TRANSFER_TIMEOUT_LENGTH = 90
    TARGET_ATTR = _response_body
    CONNECTION_TIMEOUT_LENGTH = 60
    -> JSONExtractor_2
JSONExtractor_2
    JSON_DOCUMENT = @Value(_response_body)
    EXTRACT_QUERY_TABLE = skattesats json["values"][0]["values"][0]["value"]
    EVALUATED -> AttributeManager_2
    EVALUATED -> JSONExtractor_2_Evaluated
AttributeManager_2
    ATTR_TABLE:
      REMOVE lansnamn
      REMOVE lanskod
      REMOVE booli_id
      REMOVE _headers{}.name
      REMOVE _headers{}.value
      REMOVE _response_body
      REMOVE _http_status_code
      REMOVE newKod
    -> FeatureMerger [SUPPLIER]
FeatureMerger
    IGNORE_NULLS = No
    REJECT_NULL_MISSING_KEYS = No
    SUPPLIERS_FIRST = No
    PROCESS_DUPS = No
    MERGE_TYPE = Attributes Only
    ATTR_CONFLICT_RES = Use Requestor
    JOIN_KEYS = @Value(kommunkod) @Value(kommunkod) AUTO
    ATTR_ACCUM_MODE = Merge Supplier
    MERGED -> Tester_2
    MERGED -> FeatureMerger_Merged
Tester_2
    TEST_MODE = Automatic
    TEST_CLAUSE = TEST @Value(NMI) = None
    BOOL_OP = OR
    TEST_DESCRIPTION = ""
    PASSED -> AttributeValueMapper
    FAILED -> h4s.statistik (writer POSTGIS_2)
AttributeValueMapper
    VAL_ATTR = NMI
    LUT = @Value(NMI),FME_NULL_VALUE
    SRC = NMI
    DIRECTION = Forward (Source To Destination)
    -> h4s.statistik (writer POSTGIS_2)
h4s.statistik (writer POSTGIS_2)
    attributes: kommunkod varchar(200), nmi int8, kommunnamn varchar(200), skattesats float8
FeatureMerger_Merged: Inspector
JSONExtractor_2_Evaluated: Inspector
