FME workspace lanMaker.fmw

Parameters:
- SourceDataset_ESRISHAPE = C:\Users\sefild\Downloads\ok_riks_Sweref_99_TM_shape\oversikt\riks\ak_riks.shp   # Source Esri Shapefile(s)
- DestDataset_SVG = C:\Hack4Swe\RESTenAvSverige\data\svg\SWARJE_lan.svg   # Destination SVG (ScalableVectorGraphics) File
- SourceDataset_ESRISHAPE_9 = C:\Users\sefild\Downloads\ok_riks_Sweref_99_TM_shape\oversikt\riks\an_riks.shp   # Source Esri Shapefile(s)
- SourceDataset_ESRISHAPE_7 = C:\Users\sefild\Downloads\ok_riks_Sweref_99_TM_shape\oversikt\riks\mh_riks.shp   # Source Esri Shapefile(s)
- SourceDataset_ESRISHAPE_10 = C:\Users\sefild\Downloads\ok_riks_Sweref_99_TM_shape\oversikt\riks\ms_riks.shp   # Source Esri Shapefile(s)
- DestDataset_POSTGIS = amazonHilding   # Connection
- DestDataset_SVG_5 = C:\Users\sefild\Downloads\ok_riks_Sweref_99_TM_shape\oversikt\riks\SWARJE_kommuner.svg   # Destination SVG (ScalableVectorGraphics) File
- DestDataset_SVG_4 = C:\Hack4Swe\RESTenAvSverige\data\svg\SWARJE_lan.svg   # Destination SVG (ScalableVectorGraphics) File

Readers:
- ESRISHAPE_1: ESRISHAPE from $(SourceDataset_ESRISHAPE) in EPSG:3006
- ESRISHAPE_2: ESRISHAPE from $(SourceDataset_ESRISHAPE_9)
- ESRISHAPE_3: ESRISHAPE from $(SourceDataset_ESRISHAPE_7)
- ESRISHAPE_6: ESRISHAPE from $(SourceDataset_ESRISHAPE_10)

Writers:
- SVG_1: SVG to $(DestDataset_SVG)
- POSTGIS_1: POSTGIS to $(DestDataset_POSTGIS)
- SVG_2: SVG to $(DestDataset_SVG_5)
- SVG_3: SVG to $(DestDataset_SVG_4)

ms_riks (reader ESRISHAPE_6)
    attributes: KKOD short, KATEGORI char(50), NAMN1 char(50), NAMN2 char(50), V_TYP char(10), ADAT char(16)
    -> Tester_2
Tester_2
    TEST_MODE = Automatic
    TEST_CLAUSE = TEST @Value(NAMN1) ATTRIBUTE_HAS_VALUE ""
    BOOL_OP = OR
    TEST_DESCRIPTION = ""
    PASSED -> Aggregator_2
Aggregator_2
    ACCUM_ATTRS_NAME = Get Attributes From One Representative Feature
    SEP = ,
    ORDERED = No
    MODE = Geometry - Assemble One Level
    AGGREGATE_TYPE = Homogeneous Collection (If Possible)
    GROUP_BY = NAMN1
    AGGREGATE -> Dissolver
Dissolver
    NO_OVRLP = No
    GROUP_BY = NAMN1
    ACCUM_INPUT_ATTRS = Get Attributes From One Representative Feature
    CONNECT_Z_MODE = First Wins
    AREA -> AreaCalculator_2
AreaCalculator_2
    MULT = 1
    AREA_ATTR = _area
    AREA_TYPE = Plane Area
    -> Sorter
Sorter
    SORT_PARM = _area NUMERIC DESCENDING
    SORTED -> Sampler
Sampler
    RATE = 7
    SAMPLE_TYPE_LONG = First N Features
    SAMPLE_MODE = No
    SAMPLED -> ms_riks
    SAMPLED -> Clipper_2 [CLIPPER]
ms_riks: Inspector [off]
mh_riks (reader ESRISHAPE_3)
    attributes: KKOD short, KATEGORI char(50), ADAT char(16)
    -> Generalizer
    -> mk_riks
Generalizer
    TOLERANCE = 1000
    PRESERVE = Yes
    ALG_TEXT = Douglas (Generalize)
    -> DonutHoleFilter
    -> Generalizer_Output
Generalizer_Output: Inspector [off]
DonutHoleFilter
    FILTER = 1000000
    -> Clipper [CLIPPER]
    -> DonutHoleFilter_Output
DonutHoleFilter_Output: Inspector [off]
mk_riks: Inspector [off]
ak_riks (reader ESRISHAPE_1)
    attributes: KOMMUNNAMN char(30), KKOD short, KATEGORI char(50), LANSNAMN char(30), KOMMUNKOD short, LANSKOD short, KOM_KOD char(4), LAN_KOD char(2), ADAT char(16)
    -> HTTPCaller [off]
    -> MaekSVG (writer SVG_1)
    -> ak_riks_2
    -> Clipper [CLIPPEE]
Clipper
    CLIP_TYPE = Multiple Clippers
    PRESERVE_CLIPPEE_EXTENTS = No
    CLIPPED_ATTR = _clipped
    ATTR_CONFLICT_RES = Use Clippee
    BOUNDARY_CASES = Treat as Inside
    ATTR_ACCUM_MODE = Merge Clipper
    CREATE_AGGREGATES = Yes
    CONNECT_Z_MODE = First Wins
    LINES_AS_SEGMENTS = No
    OUTSIDE -> Deaggregator
    <REJECTED> -> Clipper__Rejected_
Deaggregator
    PART_NUMBER_FIELD = _part_number
    LIST_ATTR_MODE_LOOKUP = LEAN
    MODE = Flatten One Level
    GEOM_NAME_FIELD = _geometry_name
    SPLIT_COMPOSITES = No
    EXPLODE_INSTANCES = No
    DEAGGREGATED -> AreaCalculator
AreaCalculator
    MULT = 1
    AREA_ATTR = _area
    AREA_TYPE = Plane Area
    -> CircularityCalculator
CircularityCalculator
    CALC_GEOM_DISP = CONVEX_HULL
    CIRC_ATTR = _circularity
    -> Sorter_2
Sorter_2
    SORT_PARM = _circularity NUMERIC DESCENDING
    SORTED -> Tester_3
Tester_3
    TEST_MODE = Automatic
    TEST_CLAUSE = TEST @Value(_circularity) > 0.35
    BOOL_OP = OR
    TEST_DESCRIPTION = ""
    PASSED -> Tester_4
Tester_4
    TEST_MODE = Automatic
    TEST_CLAUSE:
      TEST @Value(KOM_KOD) = 980
      TEST @Value(_part_number) RANGE [34,35]
      TEST @Value(KOMMUNKOD) != 980
    BOOL_OP = COMPOSITE
    TEST_DESCRIPTION = ""
    COMPOSITE_TEST = "(1 AND 2) OR 3"
    PASSED -> Aggregator_3
Aggregator_3
    ACCUM_ATTRS_NAME = Get Attributes From One Representative Feature
    SEP = ,
    ORDERED = No
    MODE = Geometry - Assemble One Level
    AGGREGATE_TYPE = Homogeneous Collection (If Possible)
    GROUP_BY = KOM_KOD
    AGGREGATE -> Clipper_Outside
    AGGREGATE -> AttributeManager_2
Clipper_Outside: Inspector [off]
AttributeManager_2
    ATTR_TABLE:
      REMOVE KOM_KOD
      REMOVE KKOD
      REMOVE KATEGORI
      REMOVE LAN_KOD
      REMOVE ADAT
      REMOVE _clipped
      REMOVE _fme_no_clipper
      REMOVE _geometry_name
      REMOVE _part_number
      REMOVE _area
      REMOVE _circularity
    -> Clipper_2 [CLIPPEE]
Clipper_2
    CLIP_TYPE = Multiple Clippers
    PRESERVE_CLIPPEE_EXTENTS = No
    CLIPPED_ATTR = _clipped
    ATTR_CONFLICT_RES = Use Clippee
    BOUNDARY_CASES = Treat as Inside
    ATTR_ACCUM_MODE = Merge Clipper
    CREATE_AGGREGATES = Yes
    CONNECT_Z_MODE = First Wins
    LINES_AS_SEGMENTS = No
    INSIDE -> Clipper_2_Inside
    OUTSIDE -> Clipper_2_Outside
    OUTSIDE -> AttributeManager_3
Clipper_2_Inside: Inspector [off]
Clipper_2_Outside: Inspector [off]
AttributeManager_3
    ATTR_TABLE:
      REMOVE _clipped
      REMOVE _fme_no_clipper
    -> HTTPCaller [off]
    -> Dissolver_2
    -> SwarjeKom (writer SVG_2)
SwarjeKom (writer SVG_2)
    attributes: KOMMUNNAMN char(30), LANSNAMN char(30), KOMMUNKOD smallint, LANSKOD smallint
Dissolver_2
    NO_OVRLP = No
    GROUP_BY = LANSKOD
    ACCUM_INPUT_ATTRS = Get Attributes From One Representative Feature
    CONNECT_Z_MODE = First Wins
    AREA -> Aggregator_5
Aggregator_5
    ACCUM_ATTRS_NAME = Get Attributes From One Representative Feature
    SEP = ,
    ORDERED = No
    MODE = Geometry - Assemble One Level
    AGGREGATE_TYPE = Homogeneous Collection (If Possible)
    GROUP_BY = LANSKOD
    AGGREGATE -> Dissolver_2_Area
    AGGREGATE -> swarjeLan (writer SVG_3)
Dissolver_2_Area: Inspector
swarjeLan (writer SVG_3)
    attributes: LANSKOD smallint, KOMMUNNAMN char(30), LANSNAMN char(30), KOMMUNKOD smallint
Clipper__Rejected_: Inspector [off]
MaekSVG (writer SVG_1) [off]
    attributes: KOMMUNNAMN char(30), KKOD smallint, KATEGORI char(50), LANSNAMN char(30), KOMMUNKOD smallint, LANSKOD smallint, KOM_KOD char(4), LAN_KOD char(2), ADAT char(16)
ak_riks_2: Inspector
an_riks (reader ESRISHAPE_2) [off]
    attributes: LANSNAMN char(30), KKOD short, KATEGORI char(50), LANSKOD short, LAN_KOD char(2), ADAT char(16)
Creator [off]
    NUM = 1
    GEOMTYPE = Geometry Object
    CREATED -> HTTPCaller
HTTPCaller
    ERROR_ATTR = _error
    USE_COOKIES = No
    RESPONSE_HEADER_LIST_ATTR = _headers
    HTTP_METHOD = GET
    STATUS_CODE_ATTR = _http_status_code
    VERIFY_SSL_CERTIFICATES = Yes
    TARGET_ATTR_ENCODING = utf-8
    FOLLOW_REDIRECTS = Yes
    TARGET_URL = https://www.booli.se/api/proxy?
    SAVE_FILE = Attribute
    TRANSFER_TIMEOUT_LENGTH = 90
    TARGET_ATTR = _response_body
    ADDITIONAL_URL_PARAMETERS = url;/areas?q=@Value(KOMMUNNAMN)
    CONNECTION_TIMEOUT_LENGTH = 60
    -> JSONExtractor
JSONExtractor
    JSON_DOCUMENT = @Value(_response_body)
    EXTRACT_QUERY_TABLE = body json["body"]
    EVALUATED -> JSONExtractor_2
JSONExtractor_2
    JSON_DOCUMENT = @Value(body)
    EXTRACT_QUERY_TABLE = areaID json["areas"][0]["booliId"] areaTyp json["areas"][0]["types"][0]
    EVALUATED -> Tester
Tester
    TEST_MODE = Automatic
    TEST_CLAUSE = TEST @Value(areaTyp) != Kommun
    BOOL_OP = OR
    TEST_DESCRIPTION = ""
    PASSED -> AttributeValueMapper
    FAILED -> HTTPCaller_Output
    FAILED -> AttributeManager
HTTPCaller_Output: Inspector [off]
AttributeValueMapper
    VAL_ATTR = areaID
    LUT = 97648,59622,746938,1365,115750,233,493,1615,115351,3123,386685,1040
    SRC = areaID
    DIRECTION = Forward (Source To Destination)
    -> AttributeValueMapper_Output
    -> AttributeManager
AttributeManager
    ATTR_TABLE:
      REMOVE KKOD
      REMOVE KATEGORI
      REMOVE KOM_KOD
      REMOVE LAN_KOD
      REMOVE ADAT
      REMOVE _creation_instance
      REMOVE _headers{}.name
      REMOVE _headers{}.value
      REMOVE _response_body
      REMOVE _http_status_code
      REMOVE body
      RENAME_SET_VALUE areaID > booli_id
      REMOVE areaTyp
    -> BulkAttributeRenamer
BulkAttributeRenamer
    PATTERN_ACTION_DISP = CASECHANGE
    CASE_CHANGE_TYPE = lower
    MODE_CHOICE = RENAME
    ATTRCHOICE = All Attributes
    -> AttributeManager_Output
    -> h4s.kommuner (writer POSTGIS_1)
AttributeManager_Output: Inspector
h4s.kommuner (writer POSTGIS_1) [off]
    attributes: kommunkod varchar(200), kommunnamn varchar(200), lansnamn varchar(200), lanskod varchar(200), booli_id varchar(200)
AttributeValueMapper_Output: Inspector [off]

FME custom transformer DonutHoleFilter
Removes small holes from donuts and converts any 
    fme_donut
    into 
    fme_polygon
    or 
    fme_ellipse
    if no holes left.
Input Ports 
Input 
The area features with or without holes which will have some or all holes removed. 
Output Ports 
Output 
All area features.
<Rejected> 
All features with fme_type other than fme_area. 
Parameters 
Minimum Hole Area 
Minimum Hole Area specifies the area, in ground units, of the smallest hole(s) that will not be removed. 
Usage Notes 
Geometries other than fme_area will be rejected. 
Heterogeneous collections will be rejected.
Any aggregate with only one member will become fme_polygon or fme_ellipse.

Parameters:
- FILTER =   # Minimum Hole Area

Input (input)
    -> GeometryFilter
GeometryFilter
    GEOM_PORT_NAMES = Area Null
    BREAK_AGG = No
    AREA -> Counter
    NULL -> AttributeCreator_2
    <UNFILTERED> -> AttributeCreator
Counter
    DOMAIN = counter
    START = 0
    CNT_ATTR = _dhfID
    SCOPE = Local
    -> DonutHoleExtractor
DonutHoleExtractor
    OUTERSHELL -> Sorter
    HOLE -> AreaCalculator
    <REJECTED> -> GeometryRefiner_2
AreaCalculator
    MULT = 1
    AREA_ATTR = _area
    AREA_TYPE = Plane Area
    -> Tester
Tester
    TEST_MODE = Automatic
    TEST_CLAUSE = TEST @Value(_area) >= $(FILTER)
    BOOL_OP = OR
    TEST_DESCRIPTION = ""
    PASSED -> Sorter
Sorter
    SORT_PARM = _dhfID ALPHA ASCENDING
    SORTED -> DonutBuilder
DonutBuilder
    GROUP_BY = _dhfID
    FLAG_ATTR = _hole_flag
    ALLOW_CYCLES = No
    DROP = yes
    CONNECT_Z_MODE = First Wins
    AREA -> Aggregator
Aggregator
    ACCUM_ATTRS_NAME = Yes
    SEP = ,
    ORDERED = No
    MODE = Geometry - Assemble One Level
    AGGREGATE_TYPE = Homogeneous Collection (If Possible)
    GROUP_BY = _dhfID
    AGGREGATE -> GeometryRefiner_2
GeometryRefiner_2
    -> Output (output)
Output (output)
AttributeCreator_2
    ATTR_TABLE = SET_TO fme_rejection_code = MISSING_GEOMETRY
    -> <Rejected> (output)
AttributeCreator
    ATTR_TABLE = SET_TO fme_rejection_code = INVALID_GEOMETRY_TYPE
    -> <Rejected> (output)
<Rejected> (output)
